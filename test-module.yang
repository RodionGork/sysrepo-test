module test-module {
  namespace "urn:example:test-module";
  prefix tm;

  container elements {
    list elem {
      key "id";
      leaf id {
        type int32;
      }
      leaf name {
        type string;
      }
      leaf comment {
        type string;
      }
      leaf online {
        config false;
        type string;
      }
      leaf active {
        config false;
        type string;
      }
    }
  }
}
